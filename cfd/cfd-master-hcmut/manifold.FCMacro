# Auto-generated by generate_manifold.py (Phase 3-5)
import math
import os
import time
import FreeCAD as App
import Part
from FreeCAD import Vector

PRIMITIVES = [
  {
    "name": "pipe_100",
    "type": "cylinder",
    "role": "pipe_segment",
    "radius_m": 0.125,
    "start_m": [
      0.0,
      0.0,
      0.0
    ],
    "end_m": [
      1.875,
      0.0,
      0.0
    ]
  },
  {
    "name": "pipe_120",
    "type": "cylinder",
    "role": "pipe_segment",
    "radius_m": 0.125,
    "start_m": [
      2.0,
      0.0,
      2.0
    ],
    "end_m": [
      2.0,
      -0.875,
      2.0
    ]
  },
  {
    "name": "pipe_130",
    "type": "cylinder",
    "role": "pipe_segment",
    "radius_m": 0.125,
    "start_m": [
      2.0,
      0.0,
      2.0
    ],
    "end_m": [
      2.0,
      0.875,
      2.0
    ]
  },
  {
    "name": "pipe_140",
    "type": "cylinder",
    "role": "pipe_segment",
    "radius_m": 0.125,
    "start_m": [
      2.0,
      0.0,
      2.0
    ],
    "end_m": [
      2.01,
      0.0,
      2.0
    ]
  },
  {
    "name": "pipe_141",
    "type": "cylinder",
    "role": "pipe_segment",
    "radius_m": 0.125,
    "start_m": [
      2.01,
      0.0,
      2.0
    ],
    "end_m": [
      3.518995209,
      0.0,
      2.0
    ]
  },
  {
    "name": "pipe_151",
    "type": "cylinder",
    "role": "pipe_segment",
    "radius_m": 0.125,
    "start_m": [
      2.125,
      -1.0,
      2.0
    ],
    "end_m": [
      3.9949748539999996,
      -1.0,
      2.0
    ]
  },
  {
    "name": "pipe_161",
    "type": "cylinder",
    "role": "pipe_segment",
    "radius_m": 0.125,
    "start_m": [
      2.125,
      1.0,
      2.0
    ],
    "end_m": [
      3.9949748539999996,
      1.0,
      2.0
    ]
  },
  {
    "name": "elbow_20",
    "type": "elbow_sweep",
    "role": "elbow_sweep",
    "corner_m": [
      2.0,
      0.0,
      0.0
    ],
    "incoming_direction": [
      1.0,
      0.0,
      0.0
    ],
    "outgoing_direction": [
      0.0,
      0.0,
      1.0
    ],
    "arc_start_m": [
      1.875,
      0.0,
      0.0
    ],
    "arc_end_m": [
      2.0,
      0.0,
      0.125
    ],
    "arc_center_m": [
      1.875,
      0.0,
      0.125
    ],
    "arc_bend_radius_m": 0.125,
    "arc_tube_radius_m": 0.125,
    "start_m": [
      1.875,
      0.0,
      0.0
    ],
    "end_m": [
      2.0,
      0.0,
      0.125
    ]
  },
  {
    "name": "elbow_40",
    "type": "elbow_sweep",
    "role": "elbow_sweep",
    "corner_m": [
      2.0,
      -1.0,
      2.0
    ],
    "incoming_direction": [
      0.0,
      -1.0,
      0.0
    ],
    "outgoing_direction": [
      1.0,
      0.0,
      0.0
    ],
    "arc_start_m": [
      2.0,
      -0.875,
      2.0
    ],
    "arc_end_m": [
      2.125,
      -1.0,
      2.0
    ],
    "arc_center_m": [
      2.125,
      -0.875,
      2.0
    ],
    "arc_bend_radius_m": 0.125,
    "arc_tube_radius_m": 0.125,
    "start_m": [
      2.0,
      -0.875,
      2.0
    ],
    "end_m": [
      2.125,
      -1.0,
      2.0
    ]
  },
  {
    "name": "elbow_50",
    "type": "elbow_sweep",
    "role": "elbow_sweep",
    "corner_m": [
      2.0,
      1.0,
      2.0
    ],
    "incoming_direction": [
      0.0,
      1.0,
      0.0
    ],
    "outgoing_direction": [
      1.0,
      0.0,
      0.0
    ],
    "arc_start_m": [
      2.0,
      0.875,
      2.0
    ],
    "arc_end_m": [
      2.125,
      1.0,
      2.0
    ],
    "arc_center_m": [
      2.125,
      0.875,
      2.0
    ],
    "arc_bend_radius_m": 0.125,
    "arc_tube_radius_m": 0.125,
    "start_m": [
      2.0,
      0.875,
      2.0
    ],
    "end_m": [
      2.125,
      1.0,
      2.0
    ]
  },
  {
    "name": "pipe_110_after_elbow",
    "type": "cylinder",
    "radius_m": 0.125,
    "start_m": [
      2.0,
      0.0,
      0.12499999999999999
    ],
    "end_m": [
      2.0,
      0.0,
      2.0
    ]
  },
  {
    "name": "reducer_142",
    "type": "cone",
    "role": "reducer",
    "radius1_m": 0.125,
    "radius2_m": 0.0715550232,
    "start_m": [
      3.518995209,
      0.0,
      2.0
    ],
    "end_m": [
      4.0,
      0.0,
      2.0
    ]
  },
  {
    "name": "reducer_152",
    "type": "cone",
    "role": "reducer",
    "radius1_m": 0.125,
    "radius2_m": 0.1244416504,
    "start_m": [
      3.9949748539999996,
      -1.0,
      2.0
    ],
    "end_m": [
      3.9999999999999996,
      -1.0,
      2.0
    ]
  },
  {
    "name": "reducer_162",
    "type": "cone",
    "role": "reducer",
    "radius1_m": 0.125,
    "radius2_m": 0.1244416504,
    "start_m": [
      3.9949748539999996,
      1.0,
      2.0
    ],
    "end_m": [
      3.9999999999999996,
      1.0,
      2.0
    ]
  }
]
PATCH_TARGETS = {
  "inlet": [
    0.0,
    0.0,
    0.0
  ],
  "outlet_33": [
    4.0,
    0.0,
    2.0
  ],
  "outlet_43": [
    3.9999999999999996,
    -1.0,
    2.0
  ],
  "outlet_53": [
    3.9999999999999996,
    1.0,
    2.0
  ]
}
BASE_NAME = "manifold"
BUILD_ID = "18b63acdb198ccf3-82d94e66"
SAVE_FCSTD = os.environ.get("MANIFOLD_SAVE_FCSTD", "0").strip().lower() in ('1', 'true', 'yes')
STL_DEFLECTION = float(os.environ.get("MANIFOLD_STL_DEFLECTION", "0.01"))


def _safe_name(name: str, used: set[str]) -> str:
    cleaned = "".join(ch if ch.isalnum() or ch == "_" else "_" for ch in name)
    if not cleaned:
        cleaned = "primitive"
    if cleaned[0].isdigit():
        cleaned = "p_" + cleaned
    base = cleaned
    i = 1
    while cleaned in used:
        i += 1
        cleaned = f"{base}_{i}"
    used.add(cleaned)
    return cleaned


def _vector(point):
    return Vector(float(point[0]), float(point[1]), float(point[2]))


def _cylinder_between(start, end, radius):
    axis = end - start
    height = axis.Length
    if height <= 1e-9:
        return None
    return Part.makeCylinder(float(radius), height, start, axis)


def _cone_between(start, end, r1, r2):
    axis = end - start
    height = axis.Length
    if height <= 1e-9:
        return None
    return Part.makeCone(float(r1), float(r2), height, start, axis)


def _clamp(value, low, high):
    return max(low, min(high, value))


def _distance(a, b):
    return (a - b).Length


def _is_planar(face):
    return hasattr(face, "Surface") and face.Surface.__class__.__name__ == "Plane"


def _extract_patch_faces(union_shape):
    all_faces = list(union_shape.Faces)
    picked = {}
    picked_indices = set()

    for patch_name, point in PATCH_TARGETS.items():
        target = _vector(point)
        best_index = None
        best_distance = float("inf")

        for face_index, face in enumerate(all_faces):
            if face_index in picked_indices:
                continue
            distance = _distance(face.CenterOfMass, target)
            if distance < best_distance:
                best_distance = distance
                best_index = face_index

        if best_index is not None:
            picked[patch_name] = all_faces[best_index]
            picked_indices.add(best_index)

    wall_faces = [face for index, face in enumerate(all_faces) if index not in picked_indices]
    return picked, wall_faces


def _rotate_about_axis(vector, axis_unit, angle_rad):
    cos_a = math.cos(angle_rad)
    sin_a = math.sin(angle_rad)
    term_a = vector * cos_a
    term_b = axis_unit.cross(vector) * sin_a
    term_c = axis_unit * (axis_unit.dot(vector) * (1.0 - cos_a))
    return term_a + term_b + term_c


def _make_elbow_sweep(start_point, end_point, center_point, bend_radius, tube_radius):
    start = _vector(start_point)
    end = _vector(end_point)
    center = _vector(center_point)

    start_vec = start - center
    end_vec = end - center
    if start_vec.Length <= 1e-9 or end_vec.Length <= 1e-9:
        return None

    normal = start_vec.cross(end_vec)
    if normal.Length <= 1e-9:
        return None
    normal.normalize()

    # Optional consistency check: start/end should be on bend radius from center.
    if abs(start_vec.Length - float(bend_radius)) > 1e-5 or abs(end_vec.Length - float(bend_radius)) > 1e-5:
        return None

    start_unit = start_vec / start_vec.Length
    end_unit = end_vec / end_vec.Length
    angle = math.acos(_clamp(start_unit.dot(end_unit), -1.0, 1.0))
    mid_vec = _rotate_about_axis(start_vec, normal, 0.5 * angle)
    mid = center + mid_vec

    arc_edge = Part.Arc(start, mid, end).toShape()
    path_wire = Part.Wire([arc_edge])

    tangent = normal.cross(start_vec)
    if tangent.Length <= 1e-9:
        tangent = end - start
    # Ensure tangent direction points from start toward end along the arc.
    if tangent.Length > 1e-9 and tangent.dot(end - start) < 0:
        tangent = tangent * -1.0
    if tangent.Length <= 1e-9:
        return None

    profile = Part.Wire([Part.Circle(start, tangent, float(tube_radius)).toShape()])
    return path_wire.makePipeShell([profile], True, True)


def _triangle_normal(a, b, c):
    normal = (b - a).cross(c - a)
    if normal.Length <= 1e-12:
        return Vector(0.0, 0.0, 0.0)
    normal.normalize()
    return normal


def _shape_triangles(shape, deflection=None):
    if deflection is None:
        deflection = STL_DEFLECTION
    points, facets = shape.tessellate(float(deflection))
    for facet in facets:
        yield points[facet[0]], points[facet[1]], points[facet[2]]


def _write_ascii_stl(shape, output_path, solid_name, deflection=None):
    triangle_count = 0
    with open(output_path, "w", encoding="ascii", newline="\n") as handle:
        handle.write("solid %s\n" % solid_name)
        for a, b, c in _shape_triangles(shape, deflection=deflection):
            triangle_count += 1
            normal = _triangle_normal(a, b, c)
            handle.write("  facet normal %.9e %.9e %.9e\n" % (normal.x, normal.y, normal.z))
            handle.write("    outer loop\n")
            handle.write("      vertex %.9e %.9e %.9e\n" % (a.x, a.y, a.z))
            handle.write("      vertex %.9e %.9e %.9e\n" % (b.x, b.y, b.z))
            handle.write("      vertex %.9e %.9e %.9e\n" % (c.x, c.y, c.z))
            handle.write("    endloop\n")
            handle.write("  endfacet\n")
        handle.write("endsolid %s\n" % solid_name)
    return triangle_count


def _concat_ascii_stls(output_path, input_paths):
    with open(output_path, "w", encoding="ascii", newline="\n") as out_handle:
        for path in input_paths:
            if not os.path.isfile(path):
                continue
            with open(path, "r", encoding="ascii", errors="ignore") as in_handle:
                content = in_handle.read()
            out_handle.write(content)
            if not content.endswith("\n"):
                out_handle.write("\n")


doc = App.newDocument("Manifold_" + BUILD_ID)
created = []
used_names = set()

for primitive in PRIMITIVES:
    ptype = primitive.get("type")
    shape = None
    start = _vector(primitive["start_m"])
    end = _vector(primitive["end_m"])

    if ptype == "cylinder":
        shape = _cylinder_between(start, end, primitive["radius_m"])
    elif ptype == "cone":
        shape = _cone_between(start, end, primitive["radius1_m"], primitive["radius2_m"])
    elif ptype == "elbow_sweep":
        bend_radius = primitive.get("arc_bend_radius_m", primitive.get("arc_radius_m", 0.0))
        tube_radius = primitive.get("arc_tube_radius_m", bend_radius)
        shape = _make_elbow_sweep(
            primitive["arc_start_m"],
            primitive["arc_end_m"],
            primitive["arc_center_m"],
            bend_radius,
            tube_radius,
        )

    if shape is None:
        continue

    obj = doc.addObject("Part::Feature", _safe_name(primitive.get("name", "primitive"), used_names))
    obj.Shape = shape
    created.append(obj)

if created:
    compound_shape = Part.makeCompound([obj.Shape for obj in created])
    compound_obj = doc.addObject("Part::Feature", "manifold_primitives_" + BUILD_ID)
    compound_obj.Shape = compound_shape

union_obj = None
patch_objects = []
patch_shapes = {}
if created:
    fused_shape = created[0].Shape.copy()
    for obj in created[1:]:
        fused_shape = fused_shape.fuse(obj.Shape)
    fused_shape = fused_shape.removeSplitter()

    union_obj = doc.addObject("Part::Feature", "manifold_union_" + BUILD_ID)
    union_obj.Shape = fused_shape

    patch_faces, wall_faces = _extract_patch_faces(fused_shape)
    for patch_name in ["inlet", "outlet_33", "outlet_43", "outlet_53"]:
        face = patch_faces.get(patch_name)
        if face is None:
            continue
        patch_shape = Part.Compound([face.copy()])
        patch_shapes[patch_name] = patch_shape
        patch_obj = doc.addObject("Part::Feature", _safe_name(patch_name, used_names))
        patch_obj.Shape = patch_shape
        patch_objects.append(patch_obj)

    if wall_faces:
        wall_shape = Part.Compound([face.copy() for face in wall_faces])
        patch_shapes["wall"] = wall_shape
        wall_obj = doc.addObject("Part::Feature", _safe_name("wall", used_names))
        wall_obj.Shape = wall_shape
        patch_objects.append(wall_obj)

doc.recompute()

script_path = globals().get("__file__", "")
if script_path:
    out_dir = os.path.join(os.path.dirname(os.path.abspath(script_path)), "geometry")
else:
    out_dir = os.path.join(os.getcwd(), "geometry")

os.makedirs(out_dir, exist_ok=True)

fcstd_path = os.path.join(out_dir, BASE_NAME + ".FCStd")
step_path = os.path.join(out_dir, BASE_NAME + ".step")

# Also write build-stamped copies so you can visually identify exact builds.
fcstd_stamped_path = os.path.join(out_dir, BASE_NAME + "_" + BUILD_ID + ".FCStd")
step_stamped_path = os.path.join(out_dir, BASE_NAME + "_" + BUILD_ID + ".step")

if created:
    start_time = time.time()
    export_shapes = [union_obj] if union_obj is not None else created
    Part.export(export_shapes, step_path)
    Part.export(export_shapes, step_stamped_path)
    print("[manifold] STEP export done in %.2fs" % (time.time() - start_time))

    # Phase 4 artifacts: extracted boundary patch faces as separate objects.
    if patch_objects:
        start_time = time.time()
        patch_step_path = os.path.join(out_dir, BASE_NAME + "_patches.step")
        patch_step_stamped_path = os.path.join(out_dir, BASE_NAME + "_patches_" + BUILD_ID + ".step")
        Part.export(patch_objects, patch_step_path)
        Part.export(patch_objects, patch_step_stamped_path)
        print("[manifold] patch STEP export done in %.2fs" % (time.time() - start_time))

    # Phase 5 artifacts: ASCII STL per patch + multi-solid concatenated STL.
    if patch_shapes:
        start_time = time.time()
        print("[manifold] ASCII STL deflection=%.6f" % STL_DEFLECTION)
        patch_names = ["inlet", "wall", "outlet_33", "outlet_43", "outlet_53"]
        patch_files = []
        patch_stamped_files = []
        for patch_name in patch_names:
            patch_shape = patch_shapes.get(patch_name)
            if patch_shape is None:
                continue
            patch_path = os.path.join(out_dir, patch_name + ".stl")
            patch_stamped_path = os.path.join(out_dir, patch_name + "_" + BUILD_ID + ".stl")
            triangle_count = _write_ascii_stl(patch_shape, patch_path, patch_name)
            _write_ascii_stl(patch_shape, patch_stamped_path, patch_name)
            print("[manifold] patch %s triangles=%d" % (patch_name, triangle_count))
            patch_files.append(patch_path)
            patch_stamped_files.append(patch_stamped_path)

        manifold_ascii_path = os.path.join(out_dir, BASE_NAME + ".stl")
        manifold_ascii_stamped_path = os.path.join(out_dir, BASE_NAME + "_" + BUILD_ID + ".stl")
        _concat_ascii_stls(manifold_ascii_path, patch_files)
        _concat_ascii_stls(manifold_ascii_stamped_path, patch_stamped_files)
        print("[manifold] ASCII STL export+concat done in %.2fs" % (time.time() - start_time))

if SAVE_FCSTD:
    start_time = time.time()
    doc.saveAs(fcstd_path)
    doc.saveAs(fcstd_stamped_path)
    print("[manifold] FCStd save done in %.2fs" % (time.time() - start_time))
else:
    print("[manifold] FCStd save skipped (set MANIFOLD_SAVE_FCSTD=1 to enable)")
